// H1 C6 -- S1a: Synchronized Runner -- happy path
// Structural architecture: components, interfaces, and connections
// Generated by experiments/H1/conditions/gen_sysml.py
// Visualise with: InterconnectionView in spec42 SysML v2 Editor

package CPScoreH1_S1a_Structure {

    // -- Interface (port type) definitions -- one per interaction --
    port def GetAll;  // getAll()
    port def Flush;  // flush()

    // -- Component part definitions ----------------------
    part def Synchronization {
        port callsGetAll    : GetAll;  // calls getAll()
        port callsFlush    : Flush;  // calls flush()
    }

    part def Aggregation {
        port providesGetAll : GetAll;  // provides getAll()
    }

    part def Logging {
        port providesFlush : Flush;  // provides flush()
    }

    // -- System: component instances and connections ------
    part s1aSystem {

        part synchronization : Synchronization;
        part aggregation : Aggregation;
        part logging : Logging;

        connection : GetAll
            connect synchronization::callsGetAll
            to      aggregation::providesGetAll;

        connection : Flush
            connect synchronization::callsFlush
            to      logging::providesFlush;

    }
}
