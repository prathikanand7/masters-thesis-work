// H1 C6 -- S1a: Synchronized Runner -- happy path
// Views for spec42 SysML v2 Editor -- open this file and use the View tab
// Generated by experiments/H1/conditions/gen_sysml.py

package H1_S1a_Views {
    import CPScoreH1_S1a_Structure::*;
    import CPScoreH1_S1a_Sequence::*;

    // Structural architecture: components, interfaces, connections
    view S1aStructView : InterconnectionView {
        expose CPScoreH1_S1a_Structure::s1aSystem;
    }

    // Ordered execution sequence
    view S1aSeqView : SequenceView {
        expose CPScoreH1_S1a_Sequence::S1aSequence;
    }

}
