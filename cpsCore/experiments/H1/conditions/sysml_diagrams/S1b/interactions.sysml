// H1 C6 -- S1b: Synchronized Runner Timeout -- failure path
// Structural architecture: components, interfaces, and connections
// Generated by experiments/H1/conditions/gen_sysml.py
// Visualise with: InterconnectionView in spec42 SysML v2 Editor

package CPScoreH1_S1b_Structure {

    // -- Interface (port type) definitions -- one per interaction --
    port def GetAll;  // getAll()
    port def Flush;  // flush()
    port def Stream;  // stream()

    // -- Component part definitions ----------------------
    part def Synchronization {
        port callsGetAll    : GetAll;  // calls getAll()
        port callsFlush    : Flush;  // calls flush()
        port callsStream    : Stream;  // calls stream()
    }

    part def Aggregation {
        port providesGetAll : GetAll;  // provides getAll()
    }

    part def Logging {
        port providesFlush : Flush;  // provides flush()
        port providesStream : Stream;  // provides stream()
    }

    // -- System: component instances and connections ------
    part s1bSystem {

        part synchronization : Synchronization;
        part aggregation : Aggregation;
        part logging : Logging;

        connection : GetAll
            connect synchronization::callsGetAll
            to      aggregation::providesGetAll;

        connection : Flush
            connect synchronization::callsFlush
            to      logging::providesFlush;

        connection : Stream
            connect synchronization::callsStream
            to      logging::providesStream;

    }
}
