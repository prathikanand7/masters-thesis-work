// H1 C6 -- S1b: Synchronized Runner Timeout -- failure path
// Ordered execution sequence (from sequence.json)
// Generated by experiments/H1/conditions/gen_sysml.py
// Visualise with: SequenceView in spec42 SysML v2 Editor

package CPScoreH1_S1b_Sequence {

    private import ScalarValues::String;

    // -- spec42-compatible interaction stereotypes -------------------------
    part def InteractionScenario;
    part def Lifeline;

    part def Message {
        attribute label : String;
        ref from : Lifeline;
        ref to   : Lifeline;
    }

    part def SynchronousCall     :> Message;
    part def ReturnMessage       :> Message;
    part def AsynchronousMessage :> Message;

    part def S1bSequence :> InteractionScenario {

        part synchronization : Lifeline;  // Synchronization
        part aggregation : Lifeline;  // Aggregation
        part logging : Lifeline;  // Logging

        part m1 : SynchronousCall {
            ref from : Lifeline = synchronization;
            ref to   : Lifeline = aggregation;
            attribute :>> label = "1. getAll";
            // Note: from SynchronizedRunner.runSynchronized
        }

        part m2 : SynchronousCall {
            ref from : Lifeline = synchronization;
            ref to   : Lifeline = aggregation;
            attribute :>> label = "2. getAll";
            // Note: from SynchronizedRunner.runSynchronized
        }

        part m3 : SynchronousCall {
            ref from : Lifeline = synchronization;
            ref to   : Lifeline = logging;
            attribute :>> label = "3. flush";
            // Note: from SynchronizedRunner.runSynchronized
        }

        part m4 : SynchronousCall {
            ref from : Lifeline = synchronization;
            ref to   : Lifeline = logging;
            attribute :>> label = "4. stream";
            // Note: CPSLOG_ERROR from SynchronizedRunnerMaster.runStage (timeout)
        }

        part m5 : SynchronousCall {
            ref from : Lifeline = synchronization;
            ref to   : Lifeline = logging;
            attribute :>> label = "5. flush";
            // Note: from SynchronizedRunner.runSynchronized
        }

    }
}
