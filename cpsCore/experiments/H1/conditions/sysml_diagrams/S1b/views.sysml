// H1 C6 -- S1b: Synchronized Runner Timeout -- failure path
// Views for spec42 SysML v2 Editor -- open this file and use the View tab
// Generated by experiments/H1/conditions/gen_sysml.py

package H1_S1b_Views {
    import CPScoreH1_S1b_Structure::*;
    import CPScoreH1_S1b_Sequence::*;

    // Structural architecture: components, interfaces, connections
    view S1bStructView : InterconnectionView {
        expose CPScoreH1_S1b_Structure::s1bSystem;
    }

    // Ordered execution sequence
    view S1bSeqView : SequenceView {
        expose CPScoreH1_S1b_Sequence::S1bSequence;
    }

}
