// H1 C6 -- S2: Configuration Property Mapping
// Structural architecture: components, interfaces, and connections
// Generated by experiments/H1/conditions/gen_sysml.py
// Visualise with: InterconnectionView in spec42 SysML v2 Editor

package CPScoreH1_S2_Structure {

    // -- Interface (port type) definitions -- one per interaction --
    port def Stream;  // stream()

    // -- Component part definitions ----------------------
    part def Configuration {
        port callsStream    : Stream;  // calls stream()
    }

    part def Logging {
        port providesStream : Stream;  // provides stream()
    }

    // -- System: component instances and connections ------
    part s2System {

        part configuration : Configuration;
        part logging : Logging;

        connection : Stream
            connect configuration::callsStream
            to      logging::providesStream;

    }
}
