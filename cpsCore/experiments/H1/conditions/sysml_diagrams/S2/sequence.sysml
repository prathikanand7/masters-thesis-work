// H1 C6 -- S2: Configuration Property Mapping
// Ordered execution sequence (from sequence.json)
// Generated by experiments/H1/conditions/gen_sysml.py
// Visualise with: SequenceView in spec42 SysML v2 Editor

package CPScoreH1_S2_Sequence {

    private import ScalarValues::String;

    // -- spec42-compatible interaction stereotypes -------------------------
    part def InteractionScenario;
    part def Lifeline;

    part def Message {
        attribute label : String;
        ref from : Lifeline;
        ref to   : Lifeline;
    }

    part def SynchronousCall     :> Message;
    part def ReturnMessage       :> Message;
    part def AsynchronousMessage :> Message;

    part def S2Sequence :> InteractionScenario {

        part configuration : Lifeline;  // Configuration
        part logging : Lifeline;  // Logging

        part m1 : SynchronousCall {
            ref from : Lifeline = configuration;
            ref to   : Lifeline = logging;
            attribute :>> label = "1. stream";
            // Note: From PropertyMapper.add during optional property mapping; call executed under LogLevel::NONE (output suppressed).
        }

    }
}
