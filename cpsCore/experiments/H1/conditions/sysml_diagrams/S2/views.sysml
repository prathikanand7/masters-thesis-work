// H1 C6 -- S2: Configuration Property Mapping
// Views for spec42 SysML v2 Editor -- open this file and use the View tab
// Generated by experiments/H1/conditions/gen_sysml.py

package H1_S2_Views {
    import CPScoreH1_S2_Structure::*;
    import CPScoreH1_S2_Sequence::*;

    // Structural architecture: components, interfaces, connections
    view S2StructView : InterconnectionView {
        expose CPScoreH1_S2_Structure::s2System;
    }

    // Ordered execution sequence
    view S2SeqView : SequenceView {
        expose CPScoreH1_S2_Sequence::S2Sequence;
    }

}
