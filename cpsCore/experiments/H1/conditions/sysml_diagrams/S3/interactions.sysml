// H1 C6 -- S3: Multi-Component Runner Orchestration
// Structural architecture: components, interfaces, and connections
// Generated by experiments/H1/conditions/gen_sysml.py
// Visualise with: InterconnectionView in spec42 SysML v2 Editor

package CPScoreH1_S3_Structure {

    // -- Interface (port type) definitions -- one per interaction --
    port def Stream;  // stream()
    port def GetAll;  // getAll()
    port def Flush;  // flush()

    // -- Component part definitions ----------------------
    part def Aggregation {
        port callsStream    : Stream;  // calls stream()
        port providesGetAll : GetAll;  // provides getAll()
    }

    part def Logging {
        port providesStream : Stream;  // provides stream()
        port providesFlush : Flush;  // provides flush()
    }

    part def Synchronization {
        port callsGetAll    : GetAll;  // calls getAll()
    }

    part def Utilities {
        port callsFlush    : Flush;  // calls flush()
        port callsStream    : Stream;  // calls stream()
    }

    // -- System: component instances and connections ------
    part s3System {

        part aggregation : Aggregation;
        part logging : Logging;
        part synchronization : Synchronization;
        part utilities : Utilities;

        connection : Stream
            connect aggregation::callsStream
            to      logging::providesStream;

        connection : GetAll
            connect synchronization::callsGetAll
            to      aggregation::providesGetAll;

        connection : Flush
            connect utilities::callsFlush
            to      logging::providesFlush;

        connection : Stream
            connect utilities::callsStream
            to      logging::providesStream;

    }
}
