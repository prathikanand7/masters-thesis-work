// H1 C6 -- S3: Multi-Component Runner Orchestration
// Ordered execution sequence (from sequence.json)
// Generated by experiments/H1/conditions/gen_sysml.py
// Visualise with: SequenceView in spec42 SysML v2 Editor

package CPScoreH1_S3_Sequence {

    private import ScalarValues::String;

    // -- spec42-compatible interaction stereotypes -------------------------
    part def InteractionScenario;
    part def Lifeline;

    part def Message {
        attribute label : String;
        ref from : Lifeline;
        ref to   : Lifeline;
    }

    part def SynchronousCall     :> Message;
    part def ReturnMessage       :> Message;
    part def AsynchronousMessage :> Message;

    part def S3Sequence :> InteractionScenario {

        part aggregation : Lifeline;  // Aggregation
        part logging : Lifeline;  // Logging
        part synchronization : Lifeline;  // Synchronization
        part utilities : Lifeline;  // Utilities

        part m1 : SynchronousCall {
            ref from : Lifeline = aggregation;
            ref to   : Lifeline = logging;
            attribute :>> label = "1. stream";
            // Note: from ObjectHandleContainer.setFromAggregationIfNotSet during aggregation update
        }

        part m2 : SynchronousCall {
            ref from : Lifeline = synchronization;
            ref to   : Lifeline = aggregation;
            attribute :>> label = "2. getAll";
            // Note: from AggregatableRunner.notifyAggregationOnUpdate
        }

        part m3 : SynchronousCall {
            ref from : Lifeline = aggregation;
            ref to   : Lifeline = logging;
            attribute :>> label = "3. stream";
            // Note: from ObjectHandleContainer.setFromAggregationIfNotSet during aggregation update
        }

        part m4 : SynchronousCall {
            ref from : Lifeline = synchronization;
            ref to   : Lifeline = aggregation;
            attribute :>> label = "4. getAll";
            // Note: from AggregatableRunner.notifyAggregationOnUpdate
        }

        part m5 : SynchronousCall {
            ref from : Lifeline = utilities;
            ref to   : Lifeline = logging;
            attribute :>> label = "5. stream";
            // Note: from MultiThreadingScheduler.schedule
        }

        part m6 : SynchronousCall {
            ref from : Lifeline = utilities;
            ref to   : Lifeline = logging;
            attribute :>> label = "6. stream";
            // Note: from SignalHandler.subscribeOnExit (invoked in MultiThreadingScheduler.run NORMAL)
        }

        part m7 : SynchronousCall {
            ref from : Lifeline = utilities;
            ref to   : Lifeline = logging;
            attribute :>> label = "7. stream";
            // Note: from MultiThreadingScheduler.run (FINAL: starting scheduler thread)
        }

        part m8 : SynchronousCall {
            ref from : Lifeline = utilities;
            ref to   : Lifeline = logging;
            attribute :>> label = "8. stream";
            // Note: from MultiThreadingScheduler.runSchedule (Starting Scheduling)
        }

        part m9 : SynchronousCall {
            ref from : Lifeline = utilities;
            ref to   : Lifeline = logging;
            attribute :>> label = "9. stream";
            // Note: from MultiThreadingScheduler.runSchedule (Waking up)
        }

        part m10 : SynchronousCall {
            ref from : Lifeline = utilities;
            ref to   : Lifeline = logging;
            attribute :>> label = "10. stream";
            // Note: from MultiThreadingScheduler.runSchedule (Executing task)
        }

        part m11 : SynchronousCall {
            ref from : Lifeline = utilities;
            ref to   : Lifeline = logging;
            attribute :>> label = "11. stream";
            // Note: from MultiThreadingScheduler.runSchedule
        }

        part m12 : SynchronousCall {
            ref from : Lifeline = utilities;
            ref to   : Lifeline = logging;
            attribute :>> label = "12. stream";
            // Note: from MultiThreadingScheduler.stop (Joining event)
        }

        part m13 : SynchronousCall {
            ref from : Lifeline = utilities;
            ref to   : Lifeline = logging;
            attribute :>> label = "13. stream";
            // Note: from MultiThreadingScheduler.stop (Joined event)
        }

        part m14 : SynchronousCall {
            ref from : Lifeline = utilities;
            ref to   : Lifeline = logging;
            attribute :>> label = "14. stream";
            // Note: from MultiThreadingScheduler.runSchedule
        }

        part m15 : SynchronousCall {
            ref from : Lifeline = utilities;
            ref to   : Lifeline = logging;
            attribute :>> label = "15. stream";
            // Note: from MultiThreadingScheduler.runSchedule
        }

        part m16 : SynchronousCall {
            ref from : Lifeline = utilities;
            ref to   : Lifeline = logging;
            attribute :>> label = "16. stream";
            // Note: from MicroSimulator.stop
        }

    }
}
