// H1 C6 -- S3: Multi-Component Runner Orchestration
// Views for spec42 SysML v2 Editor -- open this file and use the View tab
// Generated by experiments/H1/conditions/gen_sysml.py

package H1_S3_Views {
    import CPScoreH1_S3_Structure::*;
    import CPScoreH1_S3_Sequence::*;

    // Structural architecture: components, interfaces, connections
    view S3StructView : InterconnectionView {
        expose CPScoreH1_S3_Structure::s3System;
    }

    // Ordered execution sequence
    view S3SeqView : SequenceView {
        expose CPScoreH1_S3_Sequence::S3Sequence;
    }

}
