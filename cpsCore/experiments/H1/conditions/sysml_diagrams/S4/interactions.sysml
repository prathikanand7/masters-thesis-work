// H1 C6 -- S4: Stage Event Bridge Pub-Sub Routing (constructed)
// Structural architecture: components, interfaces, and connections
// Generated by experiments/H1/conditions/gen_sysml.py
// Visualise with: InterconnectionView in spec42 SysML v2 Editor

package CPScoreH1_S4_Structure {

    // -- Interface (port type) definitions -- one per interaction --
    port def Stream;  // stream()
    port def SubscribeStage;  // subscribeStage()

    // -- Component part definitions ----------------------
    part def Aggregation {
        port callsStream    : Stream;  // calls stream()
        port callsSubscribeStage    : SubscribeStage;  // calls subscribeStage()
    }

    part def Logging {
        port providesStream : Stream;  // provides stream()
    }

    part def Synchronization {
        port callsStream    : Stream;  // calls stream()
        port providesSubscribeStage : SubscribeStage;  // provides subscribeStage()
    }

    // -- System: component instances and connections ------
    part s4System {

        part aggregation : Aggregation;
        part logging : Logging;
        part synchronization : Synchronization;

        connection : Stream
            connect aggregation::callsStream
            to      logging::providesStream;

        connection : SubscribeStage
            connect aggregation::callsSubscribeStage
            to      synchronization::providesSubscribeStage;

        connection : Stream
            connect synchronization::callsStream
            to      logging::providesStream;

    }
}
