// H1 C6 -- S4: Stage Event Bridge Pub-Sub Routing (constructed)
// Ordered execution sequence (from sequence.json)
// Generated by experiments/H1/conditions/gen_sysml.py
// Visualise with: SequenceView in spec42 SysML v2 Editor

package CPScoreH1_S4_Sequence {

    private import ScalarValues::String;

    // -- spec42-compatible interaction stereotypes -------------------------
    part def InteractionScenario;
    part def Lifeline;

    part def Message {
        attribute label : String;
        ref from : Lifeline;
        ref to   : Lifeline;
    }

    part def SynchronousCall     :> Message;
    part def ReturnMessage       :> Message;
    part def AsynchronousMessage :> Message;

    part def S4Sequence :> InteractionScenario {

        part synchronization : Lifeline;  // Synchronization
        part logging : Lifeline;  // Logging
        part aggregation : Lifeline;  // Aggregation

        part m1 : SynchronousCall {
            ref from : Lifeline = synchronization;
            ref to   : Lifeline = logging;
            attribute :>> label = "1. stream";
            // Note: Fault path: StageEventBridge.publishStage logs error (CPSLOG_ERROR) when no listeners are connected; output suppressed by LogLevel::NONE.
        }

        part m2 : SynchronousCall {
            ref from : Lifeline = aggregation;
            ref to   : Lifeline = logging;
            attribute :>> label = "2. stream";
            // Note: Success path: StageEventListener.onStageEvent invoked via boost::signals2 slot; logs receipt (CPSLOG_DEBUG).
        }

    }
}
