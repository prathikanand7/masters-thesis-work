// H1 C6 -- S4: Stage Event Bridge Pub-Sub Routing (constructed)
// Views for spec42 SysML v2 Editor -- open this file and use the View tab
// Generated by experiments/H1/conditions/gen_sysml.py

package H1_S4_Views {
    import CPScoreH1_S4_Structure::*;
    import CPScoreH1_S4_Sequence::*;

    // Structural architecture: components, interfaces, connections
    view S4StructView : InterconnectionView {
        expose CPScoreH1_S4_Structure::s4System;
    }

    // Ordered execution sequence
    view S4SeqView : SequenceView {
        expose CPScoreH1_S4_Sequence::S4Sequence;
    }

}
